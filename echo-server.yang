module echo-server {

    yang-version 1;

    namespace
      "http://netconfcentral.org/ns/echo-server";

    prefix echo-server;

    description
        "This yang module describes states and services of a UDP based echo 
         server, which echos back message sent by clients and also keeps 
         track of client served. Operational states of this server can be accessed 
         via REST API. This server also implements notification service by 
         which arrival of echo from a new client can be informed asynchronously";

    grouping echo-client {

        leaf client-ip {
            type string;
        }

        leaf last-echo-time {
            type string;
        }

        leaf echo-count {
            type uint32;
        }
    }

    container echo-server {
        config false;

        leaf client-count {
            type uint32;
        }

        list clients {
            key client-ip;

            uses echo-client;
        }
    }

    notification new-client {

      description
        "Indicates arrival of echo-request from new client.";

      uses echo-client;

    } 
}
