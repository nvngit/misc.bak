module wtpdiscover-model {
    namespace "urn:opendaylight:capwap:wtpdiscover-model";
    prefix "wtpdiscover-model";

    import ietf-inet-types { prefix inet; revision-date 2010-09-24; }
    import common-model { prefix common-model; revision-date 2015-02-17; }

    contact "Navin Agrawal <nagrawal@brocade.com>";

    description
        "This module contains the base data model of CAPWAP AC 
        WTP Discover component.

        This program and the accompanying materials are made available
        under the terms of the Eclipse Public License v1.0 which
        accompanies this distribution, and is available at
        http://www.eclipse.org/legal/epl-v10.html";

    revision "2015-02-17" {
        description "Initial revision of wtpdiscover model";
    }

    grouping discovered-wtp {
        reference "Section 3.3 RFC 5415";
        description "Discovered WTP Description";

        leaf ipv4-addr {
            type inet:ipv4-address;
        }

        leaf ipv6-addr {
            type inet:ipv6-address;
        }

	container board-data {
        	uses common-model:wtp-board-data;
        }

	container descriptor {
        	uses common-model:wtp-descriptor;
        }

	container frame-tunnel-mode {
        	uses common-model:wtp-frame-tunnel-mode;
        }

	container mac-type {
        	uses common-model:wtp-mac-type;
        }

	container radio-info {
        	uses common-model:wtp-radio-info;
        }

	container discovery-type {
        	uses common-model:wtp-discovery-type;
	}
    }

    container discovered-wtps {
        config false;

	list wtps {
        	uses discovered-wtp;
        }
    }
}
